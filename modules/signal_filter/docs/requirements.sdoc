[DOCUMENT]
TITLE: SignalFilter Requirements
PREFIX: REQ-

[REQUIREMENT]
UID: REQ-2
TITLE: Smooth noisy sensor signal
STATEMENT: >>>
The system shall smooth a noisy input stream using a moving-average filter
over a configurable window size.
<<<
