[DOCUMENT]
TITLE: Architecture
PREFIX: ARCH-

[REQUIREMENT]
UID: ARCH-1
TITLE: SensorInput module
STATEMENT: >>>
The ``SensorInput`` C++ class implements REQ-1 by exposing raw sensor
samples by index.
<<<
RELATIONS:
- TYPE: Parent
  VALUE: REQ-1

[REQUIREMENT]
UID: ARCH-2
TITLE: SignalFilter module
STATEMENT: >>>
The ``MovingAverageFilter`` C++ class implements REQ-2 by maintaining a
sliding window over the most recent samples.
<<<
RELATIONS:
- TYPE: Parent
  VALUE: REQ-2

[REQUIREMENT]
UID: ARCH-3
TITLE: MathUtils module
STATEMENT: >>>
The ``math_utils`` C++ functions (``Add``, ``Clamp``) implement REQ-3.
<<<
RELATIONS:
- TYPE: Parent
  VALUE: REQ-3

[REQUIREMENT]
UID: ARCH-4
TITLE: Diagnostics module
STATEMENT: >>>
The ``RangeDiagnostics`` C++ class implements REQ-4 by checking a value
against a configured [lo, hi] range.
<<<
RELATIONS:
- TYPE: Parent
  VALUE: REQ-4

[REQUIREMENT]
UID: ARCH-5
TITLE: Logger module
STATEMENT: >>>
The ``Logger`` C++ class implements REQ-5 by recording severity-tagged
entries.
<<<
RELATIONS:
- TYPE: Parent
  VALUE: REQ-5

[REQUIREMENT]
UID: ARCH-6
TITLE: Controller module
STATEMENT: >>>
The ``Controller`` C++ class implements REQ-6 by composing SensorInput,
SignalFilter, Diagnostics, Logger and MathUtils into one control cycle.
<<<
RELATIONS:
- TYPE: Parent
  VALUE: REQ-6
- TYPE: Parent
  VALUE: ARCH-1
- TYPE: Parent
  VALUE: ARCH-2
- TYPE: Parent
  VALUE: ARCH-3
- TYPE: Parent
  VALUE: ARCH-4
- TYPE: Parent
  VALUE: ARCH-5

[REQUIREMENT]
UID: ARCH-7
TITLE: SpeedController module (Simulink MBD generated)
STATEMENT: >>>
The ``speed_controller`` C module implements REQ-7. It is generated from
a Simulink model (see models/speed_controller.md) with Simulink Embedded
Coder and must not be hand-edited; regenerating it from the model is the
only supported way to change its behavior. Because of that, this
relation links directly to the generated files themselves (``TYPE: File``)
instead of relying on an in-file ``@relation(...)`` marker, which is how
the other six (hand-written) modules are linked.
<<<
RELATIONS:
- TYPE: Parent
  VALUE: REQ-7
- TYPE: File
  VALUE: src/speed_controller/speed_controller.c
- TYPE: File
  VALUE: src/speed_controller/speed_controller.h
